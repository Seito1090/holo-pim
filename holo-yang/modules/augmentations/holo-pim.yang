module holo-pim {
  yang-version 1.1;
  namespace "http://holo-routing.org/yang/holo-pim";
  prefix holo-pim;

  import ietf-interfaces {
    prefix if;
  }
  import ietf-routing {
    prefix rt;
  }

  organization
    "Holo Routing Stack";

  description
    "Configuration and operational data for the Holo PIM
     implementation.";

  identity pim {
    base rt:routing-protocol;
    description
      "Protocol Independent Multicast.";
  }

  augment "/rt:routing/rt:control-plane-protocols/rt:control-plane-protocol" {
    container pim {
      description
        "PIM instance configuration.";

      leaf enabled {
        type boolean;
        default true;
        description
          "Enable the PIM instance.";
      }

      container ipv4 {
        leaf enabled {
          type boolean;
          default true;
          description
            "Enable IPv4 PIM.";
        }
      }

      container ipv6 {
        leaf enabled {
          type boolean;
          default false;
          description
            "Enable IPv6 PIM.";
        }
      }

      list interface {
        key name;
        description
          "PIM configuration for an interface.";

        leaf name {
          type if:interface-ref;
        }
        leaf enabled {
          type boolean;
          default true;
        }
        leaf dr-priority {
          type uint32;
          default 1;
        }
        leaf hello-interval {
          type uint16;
          default 30;
          units seconds;
        }
        leaf hello-holdtime {
          type uint16;
          default 105;
          units seconds;
        }
        leaf propagation-delay {
          type uint16;
          default 500;
          units milliseconds;
        }
        leaf override-interval {
          type uint16;
          default 2500;
          units milliseconds;
        }
        leaf suppression-enabled {
          type boolean;
          default false;
        }
      }
    }
  }
}
